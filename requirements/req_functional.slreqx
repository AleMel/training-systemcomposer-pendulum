# req_functional

## ReqFun_1: Control speed (Functional)
The pendulum needs to be controlled to the target within 1 second.

## ReqFun_2: Control robustness (Functional)
The control system needs to be capable of controlling 2 types of pendulums without any change in the control parameters:
- 20 cm long
- 30 cm long
The mass of the bulb is 0.1 kg.

## ReqFun_3: Power consumption (Functional)
The motor driver shall not require more than 120 W.

## ReqFun_4: Contact Safety (Functional)
The contact shall be detected and the interaction force shall be reduced under 1N within 1s.
Once the contact is detected, the system stops receiving further set-points.
